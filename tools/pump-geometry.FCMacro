# -*- coding: utf-8 -*-
"""pump-geometry.FCMacro -- build the PUMP-SYNTH stage-2 plate geometry in FreeCAD from pump-geometry.json.

Usage (FreeCAD >= 0.19, GUI): Macro > Macros... > Execute this file, then pick the pump-geometry.json exported
by tools/pump-synth.html (stage 2). Headless: set PUMP_GEOMETRY_JSON=/path/to/pump-geometry.json and run
`freecadcmd pump-geometry.FCMacro`. The document (and a STEP) is saved next to the JSON.

What it builds (units mm, z = shaft axis, z = 0 = the septum mid-plane, electrical 0 deg = +x):
  * carriers (rotor discs, rotor flanges, stator carriers): annular discs r_in..r_out over z0..z1
  * foil electrodes: annular-sector sets (one solid per sector) on the carrier faces
  * dielectric slabs: the septum (garolite, full disc) and the Ca/Cb mica (the electrode footprint grown by
    the stated margin); air gaps are left empty
  * spark gaps: stator spheres + posts + leads (to their node's carrier, crossovers over the stator) and the rotor
    tips + arms, on two gap planes per side
Grouped by carrier (App::Part -> named STEP sub-assemblies); coloured by electrical node; every solid carries a
descriptive Label (its STEP product name) and a row in <json>-parts.csv. Geometry only -- no physics here.
The same file is executed by sim/pump_geometry_gates.py through an OpenCascade stand-in for Part (gate G-CAD),
which checks every solid's volume against the analytic value and writes the reference STEP.
"""
import json
import math
import os

import FreeCAD
import Part



def _json_path():
    p = os.environ.get("PUMP_GEOMETRY_JSON")
    if p:
        return p
    if FreeCAD.GuiUp:
        from PySide import QtGui
        p, _ = QtGui.QFileDialog.getOpenFileName(None, "pump-geometry.json", "", "JSON (*.json)")
        return p
    raise RuntimeError("set PUMP_GEOMETRY_JSON to the exported pump-geometry.json")


def annulus(r_in, r_out, z0, z1, start_deg=0.0, w_deg=360.0):
    """An annular sector solid: radius r_in..r_out, angle start..start+w, height z0..z1."""
    h = z1 - z0
    base = FreeCAD.Vector(0, 0, z0)
    axis = FreeCAD.Vector(0, 0, 1)
    full = w_deg >= 360.0 - 1e-9
    outer = Part.makeCylinder(r_out, h, base, axis) if full else Part.makeCylinder(r_out, h, base, axis, w_deg)
    if r_in > 1e-9:
        inner = Part.makeCylinder(r_in, h, base, axis) if full else Part.makeCylinder(r_in, h, base, axis, w_deg)
        outer = outer.cut(inner)
    if not full and abs(start_deg) > 1e-12:
        outer.rotate(FreeCAD.Vector(0, 0, 0), axis, start_deg)
    return outer


_IMPORTED = {}


def imported(p, base_dir):
    """A solid read from a STEP in its local frame (shape "import": file relative to the JSON), then placed:
    translate x by place.r, rotate about z by place.theta_deg, then z += place.z."""
    path = os.path.join(base_dir, p["file"])
    if path not in _IMPORTED:
        _IMPORTED[path] = Part.read(path)
    shp = _IMPORTED[path].copy()
    pl = p["place"]
    shp.translate(FreeCAD.Vector(pl["r"], 0, 0))
    shp.rotate(FreeCAD.Vector(0, 0, 0), FreeCAD.Vector(0, 0, 1), pl["theta_deg"])
    shp.translate(FreeCAD.Vector(0, 0, pl.get("z", 0.0)))
    return shp


def solid(p, base_dir=""):
    """One part of the bill of solids: an annular sector, a sphere (gap electrode), a rod (post / arm / lead) or
    an imported STEP solid (the motor)."""
    shape = p.get("shape", "sector")
    if shape == "import":
        return imported(p, base_dir)
    if shape == "sphere":
        return Part.makeSphere(p["r"], FreeCAD.Vector(*p["c"]))
    if shape == "rod":
        a, b = FreeCAD.Vector(*p["p0"]), FreeCAD.Vector(*p["p1"])
        d = b - a
        return Part.makeCylinder(p["r"], d.Length, a, d)
    return annulus(p["r_in"], p["r_out"], p["z0"], p["z1"], p["start_deg"], p["w_deg"])


def _colour(obj, rgb):
    obj.Colour = tuple(rgb)                            # kept for the STEP writer (and the OCC stand-in)
    if FreeCAD.GuiUp and rgb:
        obj.ViewObject.ShapeColor = tuple(rgb)


def build(design, doc, base_dir=""):
    """Build exactly the bill of solids in design['parts'] (names, labels, assemblies and colours are decided
    by sim/pump_geometry.py / tools/pump-geometry.js, so FreeCAD and Fusion 360 name everything identically)."""
    groups = {}
    for a in design["assemblies"]:
        g = doc.addObject("App::Part", a["key"].replace("-", "_"))
        g.Label = a["label"]
        groups[a["key"]] = g
    made = []
    for p in design["parts"]:
        shp = solid(p, base_dir)
        o = doc.addObject("Part::Feature", p["name"])
        o.Shape = shp
        o.Label = p["label"]
        _colour(o, p["rgb"])
        groups[p["assembly"]].addObject(o)
        row = dict(p)
        row.update(name=o.Name, assembly=groups[p["assembly"]].Label, expect=p["volume"], volume=shp.Volume)
        made.append(row)
    doc.recompute()
    return made, groups


PARTS_COLUMNS = ("name", "label", "assembly", "role", "shape", "carrier", "node", "cap", "material", "r_in", "r_out",
                 "start_deg", "w_deg", "z0", "z1", "c", "r", "p0", "p1", "volume")


def write_parts_table(made, path):
    """The translation table: one row per solid (its FreeCAD / STEP name -> what it is)."""
    import csv
    with open(path, "w", newline="") as fh:
        w = csv.writer(fh)
        w.writerow(PARTS_COLUMNS)
        for m in made:
            w.writerow([("%.4f" % m[c]) if isinstance(m.get(c), float) else
                        (" ".join("%.3f" % v for v in m[c]) if isinstance(m.get(c), list) else m.get(c, "")) for c in PARTS_COLUMNS])


def export_step(doc, groups, path, top_label):
    """STEP with the labels as product names, the carrier groups as named sub-assemblies, and colours:
    FreeCAD's Import exporter (OCAF) keeps all three; Part.export would write anonymous solids."""
    top = doc.addObject("App::Part", "PumpGeometry")
    top.Label = top_label
    for g in groups.values():
        top.addObject(g)
    try:
        import Import
        Import.export([top], path)
    except ImportError:
        objs = [o for o in doc.Objects if o.TypeId == "Part::Feature"]
        Part.export(objs, path)                       # fallback: geometry only, no names


def main():
    path = _json_path()
    if not path:
        return None
    design = json.load(open(path))
    if design.get("schema") != "pump-geometry/1":
        raise RuntimeError("not a pump-geometry/1 file: %r" % design.get("schema"))
    if "parts" not in design:
        raise RuntimeError("this JSON predates the bill of solids: re-export it from tools/pump-synth.html stage 2")
    doc = FreeCAD.newDocument("PumpGeometry_" + design["lock"]["hash"])
    doc.Label = design["top_label"]
    made, groups = build(design, doc, os.path.dirname(os.path.abspath(path)))
    base = os.path.splitext(path)[0]
    export_step(doc, groups, base + ".step", design["top_label"])
    write_parts_table(made, base + "-parts.csv")
    doc.recompute()
    doc.saveAs(base + ".FCStd")
    if FreeCAD.GuiUp:
        import FreeCADGui
        FreeCADGui.SendMsgToActiveView("ViewFit")
        FreeCADGui.activeDocument().activeView().viewIsometric()
    FreeCAD.Console.PrintMessage("pump-geometry: %d solids, lock %s, saved %s.FCStd / .step / -parts.csv\n"
                                 % (len(made), design["lock"]["hash"], base))
    return made


RESULT = main()
